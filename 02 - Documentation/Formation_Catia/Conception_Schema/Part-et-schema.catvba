Attribute VB_Name = "Feuille1"
Attribute VB_Base = "0{0B7A0D0B-17B9-4C7A-BAEF-A12BA4DDA34A}{310B29A6-C9F9-4766-8E9E-3D4ED7A7973A}"
Attribute VB_GlobalNameSpace = False
Attribute VB_Creatable = False
Attribute VB_PredeclaredId = True
Attribute VB_Exposed = False
Attribute VB_TemplateDerived = False
Attribute VB_Customizable = False
Private Sub Bouton_annuler_Click()
crer_piece = "non"
Feuille1.hide
End Sub

Private Sub Bouton_ok_Click()
creer_piece = "oui"
'MsgBox "nouvelle_piece_seule" & nouvelle_piece_seule
If Feuille1.Option_creer_schema.Value = "Vrai" Then
    creer_schema = "oui"
End If
Feuille1.hide
End Sub

Private Sub Option_dans_product_Click()
nouvelle_piece_seule = "non"
End Sub

Private Sub Option_nouvelle_Click()
nouvelle_piece_seule = "oui"
End Sub

Private Sub Texte_nom_piece_Change()
If Feuille1.Texte_nom_piece.Text <> "" Then
    nom_piece = Feuille1.Texte_nom_piece.Text
    Feuille1.Bouton_ok.Enabled = True
Else
    Feuille1.Bouton_ok.Enabled = False
End If
End Sub

Attribute VB_Name = "Module_des_variables"
Public creer_piece As String
Public creer_schema As String
Public nom_piece As String
Public nouvelle_piece_seule As String

Attribute VB_Name = "Part_et_schema"
Sub CATMain()
creer_piece = "non"
creer_schema = "non"
nouvelle_piece_seule = "non"
Feuille1.Texte_nom_piece.Value = ""
Feuille1.Option_creer_schema.Value = 0
On Error Resume Next
'Est-on dans un document
Dim atelier_en_cours As Variant
atelier_en_cours = CATIA.Application.GetWorkbenchId
If CATIA.Documents.Count = 0 Or (atelier_en_cours <> "Assembly" And atelier_en_cours <> "PrsConfiguration" And atelier_en_cours <> "DMUKinematics") Then
    nouvelle_piece_seule = "oui"
    Feuille1.Option_dans_product.Value = 0
    Feuille1.Option_dans_product.Enabled = False
    Feuille1.Option_nouvelle.Value = 1
Else
    Feuille1.Option_dans_product.Value = 1
    Feuille1.Option_dans_product.Enabled = True
    Feuille1.Option_nouvelle.Value = 0
End If
Feuille1.Show
If creer_piece = "oui" Then
    Dim documents1 As Variant
    Set documents1 = CATIA.Documents
    Dim part1 As Part
    Dim bodies1 As Bodies
    Dim body1 As Body
'Si option pièce seule cochée
    If nouvelle_piece_seule = "oui" Then
        Dim partDocument1 As PartDocument
        Set partDocument1 = documents1.Add("Part")
        CATIA.ActiveDocument.GetItem(1).PartNumber = nom_piece
    End If
'Si option pièce dans Product cochée
    If nouvelle_piece_seule = "non" Then
        Dim productDocument1 As ProductDocument
        Set productDocument1 = CATIA.ActiveDocument
        Dim product1 As Product
        Set product1 = productDocument1.Product
        Dim products1 As Products
        Set products1 = product1.Products
        Dim product2 As Product
        Set product2 = products1.AddNewComponent("Part", nom_piece)
        Set partDocument1 = documents1.Item(nom_piece & ".CATPart")
    End If
    If creer_schema = "oui" Then
        Set part1 = partDocument1.Part
        Set bodies1 = part1.Bodies
        Set body1 = bodies1.Add()
        body1.Name = "Schema"
'Le corps de piece SCHEMA sera l'objet de travail
        part1.InWorkObject = body1
    End If
    part1.Update
End If
End Sub
